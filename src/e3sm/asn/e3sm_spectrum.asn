-- Spectrum Service Model ASN.1 Definitions
--
-- Copyright (c) 2026 Institute for Intelligent Networked Systems (INSI)
-- at Northeastern University. All rights reserved.
-- SPDX-License-Identifier: LicenseRef-CSSL-1.0
--
-- This service model extends E3 messages for spectrum sharing applications
--
-- Usage with E3 Protocol:
-- - Spectrum-SensingIndication structures are encoded into the protocolData field of E3-IndicationMessage
-- - Spectrum-DAppControlData structures are encoded into the actionData field of E3-DAppControlAction
-- - Spectrum-DAppReportData structures are encoded into the reportData field of E3-DAppReport
-- - Spectrum-XAppControlData structures are encoded into the xAppControlData field of E3-XAppControlAction
--
-- Each "*Data" envelope is a single-member SEQUENCE holding a Payload CHOICE:
-- the CHOICE alternative is the type discriminator on the ASN.1 wire. The JSON
-- encoding adds an explicit type key (e.g. "controlType") next to the payload
-- for readability; that key is produced and checked by the codecs and is not a
-- schema field.

SPECTRUM-SM DEFINITIONS AUTOMATIC TAGS ::= BEGIN

-- ============================================================================
-- SM SPECTRUM RAN FUNCTION DATA STRUCTURES  
-- ============================================================================

-- Spectrum RAN function data
Spectrum-RanFunctionData ::= SEQUENCE {
    name                    OCTET STRING (SIZE (1..32)),
    version                 INTEGER (0..65535),
    description             OCTET STRING (SIZE (1..128))
}

-- ============================================================================
-- INDICATION MESSAGE STRUCTURES
-- ============================================================================

-- Uplink carrier the sensing ranges are indexed against, from
-- ServingCellConfigCommon.frequencyInfoUL. Emitted every cellConfigPeriodMs.
Spectrum-CellConfigIndication ::= SEQUENCE {
    timestamp            INTEGER,
    ulCarrierPRBs        INTEGER (1..maxPRBs),
    ulOffsetToCarrier    INTEGER (0..maxPRBIndex),               -- carrier start, ABSOLUTE grid PRB
    ulSubcarrierSpacing  INTEGER (0..3),                         -- 3GPP enum, 0=15 .. 3=120 kHz
    ulArfcnPointA        INTEGER (0..maxARFCN),                  -- DL point A when the UL one is absent
    slotsPerFrame        INTEGER (1..maxSlotsFrame),
    tddSlotPattern       OCTET STRING (SIZE (1..maxSlotsFrame)) OPTIONAL,  -- 'D'/'U'/'S' per slot
    nrPci                INTEGER (0..maxPCI) OPTIONAL,
    ...
}

-- Sensing-range telemetry indication (one per MAC sensing publish). The
-- sensing ranges are NOT inline: they are written out-of-band into the
-- /e3_l2_sensing POSIX shm ring; this payload carries only a reference into
-- that ring, so the message stays small (a few dozen bytes) regardless of how
-- many tiles the slot held. A dApp maps the named region read-only and reads
-- the ranges (raw sensing_range_t records) at the given write index, after
-- checking the ring slot's own (sfn, slot) tag against this indication
-- (torn/wrap guard).
--
-- timestamp   : CLOCK_MONOTONIC nanoseconds at the publish point. Monotonic, not
--               realtime, because this indication cannot leave the host: it
--               carries only a reference into the local /e3_l2_sensing shm ring,
--               so a dApp elsewhere could not dereference it. Monotonic shares an
--               origin across processes on one host, which is exactly the span
--               this measures. Never difference it against
--               Spectrum-DAppReportData.timestamp, which is realtime.
-- sfn / slot  : frame and slot the snapshot belongs to.
-- beam        : OPTIONAL - set 0..3 when the upstream sensing scheduler grows
--               multi-beam support; the writer currently always emits 0.
-- shmName     : POSIX shm region holding the ranges, e.g. "/e3_l2_sensing".
-- shmWriteIdx : ring slot index just written (the ranges for this (sfn,slot)).
-- nRanges     : number of sensing_range_t records live at that index, 0..128.
Spectrum-SensingIndication ::= SEQUENCE {
    timestamp    INTEGER,
    sfn          INTEGER (0..65535),
    slot         INTEGER (0..65535),
    beam         INTEGER (0..3) OPTIONAL,
    shmName      OCTET STRING,
    shmWriteIdx  INTEGER (0..65535),
    nRanges      INTEGER (0..128)
}

Spectrum-Indication ::= CHOICE {
    sensingIndication       Spectrum-SensingIndication,
    cellConfigIndication    Spectrum-CellConfigIndication
}

-- ============================================================================
-- CONTROL ACTION STRUCTURES  
-- ============================================================================

-- PRB Blacklist Control (main control message used by spectrum dApp)
Spectrum-PRBBlacklistControl ::= SEQUENCE {
    blacklistedPRBs   SEQUENCE (SIZE (0..maxPRBs)) OF INTEGER (0..maxPRBIndex),     -- List of PRB indices
    samplingThreshold       INTEGER (0..100) OPTIONAL,                              -- Sampling ratio for the IQ captures, one delivery each samplingThreshold
    validityPeriod          INTEGER (1..3600) OPTIONAL                              -- How long this blacklist is valid (seconds)
}

-- Sensing Policy Control: per-slot 14-bit symbol bitmap consumed by the
-- masked UL TDA selector.  Bit s set in maskPerSlot[k] => "for slot k of
-- the frame, prefer TDAs that don't claim symbol s for the UE so that
-- symbol stays free for sensing".  Length of maskPerSlot MUST equal the
-- gNB's numb_slots_frame (e.g. 20 at numerology 1).  deactivate=TRUE clears the
-- policy regardless of the mask.
Spectrum-SensingPolicyControl ::= SEQUENCE {
    maskPerSlot             SEQUENCE (SIZE (1..maxSlotsFrame)) OF INTEGER (0..maxSymbolMask),
    deactivate              BOOLEAN DEFAULT FALSE,
    validityPeriod          INTEGER (1..3600) OPTIONAL
}

-- Slots reserved entirely for sensing; an empty list reserves nothing.
Spectrum-SensingReservationControl ::= SEQUENCE {
    reservedSlots           SEQUENCE (SIZE (0..maxSlotsFrame)) OF INTEGER (0..maxSlotIndex)
}

-- Slots the capture PUSCH may use; opt-in, an empty list injects nowhere.
Spectrum-SensingPuschSlotsControl ::= SEQUENCE {
    puschSlots              SEQUENCE (SIZE (0..maxSlotsFrame)) OF INTEGER (0..maxSlotIndex)
}

-- Extensibility marker (...) keeps the ASN.1 wire bit-width stable when new
-- alternatives are added.  Without it, extending a 1-alt CHOICE to 2
-- alternatives would change the APER encoding width from 0 bits to 1 bit and
-- silently break every existing deployment.
Spectrum-DAppControlPayload ::= CHOICE {
    prbBlacklistControl     Spectrum-PRBBlacklistControl,
    ...,
    sensingPolicyControl    Spectrum-SensingPolicyControl,
    sensingReservationControl Spectrum-SensingReservationControl,
    sensingPuschSlotsControl Spectrum-SensingPuschSlotsControl
}

-- Top-level dApp control PDU carried by E3-DAppControlAction.actionData
Spectrum-DAppControlData ::= SEQUENCE {
    controlPayload          Spectrum-DAppControlPayload
}

-- ============================================================================
-- dAPP REPORT STRUCTURES
-- ============================================================================


-- PRB detection parameters of the dApp.
Spectrum-DetectionInfo ::= SEQUENCE {
    method                  INTEGER (0..255),                               -- detection method: 0 detector, 1 model
    embargoMs               INTEGER (0..3600000),                           -- detection embargo, milliseconds
    aggregationWindow       INTEGER (1..1024),                              -- detection rounds aggregated per report
    ...
}

-- PRBs reported by the dApp, with the optional policy and detection parameters.
Spectrum-PRBBlacklistReport ::= SEQUENCE {
    blacklistedPRBs         SEQUENCE (SIZE (0..maxPRBs)) OF INTEGER (0..maxPRBIndex),    -- List of PRB indices
    ...,
    policyName              OCTET STRING (SIZE (1..32)) OPTIONAL,           -- name of the enabled dApp policy
    lastXAppControlSequenceId INTEGER (0..4294967295) OPTIONAL,             -- sequenceId of the last xApp PRB control
    detection               Spectrum-DetectionInfo OPTIONAL                 -- PRB detection parameters
}

Spectrum-DAppReportPayload ::= CHOICE {
    prbBlacklistReport      Spectrum-PRBBlacklistReport,
    ...
}

-- Top-level dApp report PDU carried by E3-DAppReport.reportData
--
-- timestamp is CLOCK_REALTIME nanoseconds at the dApp, taken when the report is
-- built. The gNB relays reportData without decoding it, so the value reaches the
-- xApp unchanged.
--
-- CLOCK_REALTIME, unlike Spectrum-SensingIndication.timestamp above: this report
-- is always sent on to an xApp and therefore changes host, while the sensing
-- indication is meant to stay on the same host (it carries only a reference into
-- a local POSIX shm ring, so it is useless anywhere else). The two fields share a
-- name but not a clock and must never be differenced against each other.
--
-- OPTIONAL: absent means "no producer reference". A dApp that does not stamp is
-- sending a normal message, not a malformed one, so no codec on this path may
-- reject it. Same convention as the E3AP envelope timestamp in libe3.
Spectrum-DAppReportData ::= SEQUENCE {
    timestamp               INTEGER OPTIONAL,
    reportPayload           Spectrum-DAppReportPayload
}

-- ============================================================================
-- xAPP CONTROL ACTION STRUCTURES  
-- ============================================================================


Spectrum-PRBBlockedControl ::= SEQUENCE {
    blockedPRBs             SEQUENCE (SIZE (0..maxPRBs)) OF INTEGER (0..maxPRBIndex)
}

-- Spectrum Configuration Control
Spectrum-ConfigControl ::= SEQUENCE {
    noiseFloorThreshold     INTEGER (-100..100) OPTIONAL,                   -- Update noise floor threshold
    averagingFrames         INTEGER (1..255) OPTIONAL,                      -- Update averaging window
    enable                  BOOLEAN OPTIONAL                                -- Enable/disable spectrum monitoring
}

-- Name, validity and state of a dApp policy.
Spectrum-PolicyControl ::= SEQUENCE {
    policyName              OCTET STRING (SIZE (1..32)),                    -- policy name, e.g. "autonomousBlock"
    validityPeriod          INTEGER (1..maxPolicyValidity),                 -- validity, seconds
    enable                  BOOLEAN,                                        -- TRUE enabled, FALSE disabled
    ...
}

Spectrum-XAppControlPayload ::= CHOICE {
    prbBlockedControl       Spectrum-PRBBlockedControl,
    configControl           Spectrum-ConfigControl,
    ...,
    policyControl           Spectrum-PolicyControl
}

-- Top-level xApp control PDU carried by E3-XAppControlAction.xAppControlData
--
-- timestamp is CLOCK_REALTIME nanoseconds at the xApp, taken when the control is
-- built. The gNB forwards xAppControlData without decoding it, so the value
-- reaches the dApp unchanged. Realtime for the same reason as the report above:
-- this message always changes host.
Spectrum-XAppControlData ::= SEQUENCE {
    timestamp               INTEGER OPTIONAL,
    controlPayload          Spectrum-XAppControlPayload
}


-- ============================================================================
-- APPLY OUTCOME STRUCTURES
-- ============================================================================
--
-- What the RAN reports back about a control it applied. This is Service Model
-- territory, not E3AP or E2SM-DAPP territory: "applied" means something
-- different for every control this SM defines, and a PRB block is only "in
-- effect" once the scheduler has actually put the mask on the air, which is a
-- later instant than the handler returning. The E2SM-DAPP control outcome
-- carries this as an opaque octet string, the same way it carries a control.
--
-- Both timestamps are CLOCK_REALTIME nanoseconds at the gNB, chosen so the xApp
-- can difference them against Spectrum-DAppReportData.timestamp, which is on the
-- same clock. They are payload fields, deliberately not latrec records: latrec
-- is CLOCK_MONOTONIC and the two must never be differenced against each other.

Spectrum-PRBBlockApplyOutcome ::= SEQUENCE {
    -- Mask written into the MAC, i.e. the control handler's install returning.
    installedTimestamp      INTEGER OPTIONAL,
    -- First scheduler tick that put the mask on the air. Later than
    -- installedTimestamp by up to one slot, and by a stochastic amount: the
    -- install runs on the control thread, the tick on the MAC thread.
    onAirTimestamp          INTEGER OPTIONAL,
    -- The frame and slot of that tick, so a reader can place it in the radio
    -- frame rather than only on the wall clock.
    sfn                     INTEGER (0..1023) OPTIONAL,
    slot                    INTEGER (0..maxSlotIndex) OPTIONAL,
    ...
}

Spectrum-ApplyOutcomePayload ::= CHOICE {
    prbBlockApplyOutcome    Spectrum-PRBBlockApplyOutcome,
    ...
}

-- Top-level apply-outcome PDU, carried by the E2SM-DAPP control outcome.
--
-- timestamp is when the outcome itself was built, which is not when anything was
-- applied; the applied instants are in the payload.
Spectrum-ApplyOutcomeData ::= SEQUENCE {
    timestamp               INTEGER OPTIONAL,
    applyOutcomePayload     Spectrum-ApplyOutcomePayload
}

-- ============================================================================
-- CONSTANTS AND CONSTRAINTS
-- ============================================================================

-- Maximum values based on 5G NR specifications
maxPRBs                     INTEGER ::= 273                                 -- Maximum PRBs in 5G NR
maxPRBIndex                 INTEGER ::= 272                                 -- maxPRBs - 1
maxSlotsFrame               INTEGER ::= 160                                 -- slots per frame at 3GPP numerology 4 (worst case); 20 at numerology 1 (30 kHz SCS)
maxSlotIndex                INTEGER ::= 159                                 -- maxSlotsFrame - 1
maxSymbolMask               INTEGER ::= 16383                               -- 14-bit symbol bitmap = (1 << 14) - 1
maxARFCN                    INTEGER ::= 3279165                             -- highest NR-ARFCN, TS 38.104 table 5.4.2.1-1
maxPCI                      INTEGER ::= 1007                                -- physical cell identities 0..1007, TS 38.211
cellConfigPeriodMs          INTEGER ::= 1000                                -- Spectrum-CellConfigIndication emit period
maxPolicyValidity           INTEGER ::= 4294967295                          -- seconds, uint32 maximum

-- ============================================================================
-- DEPRECATED: LEGACY eCPRI IQ PATH (E3Controller only, not in the Spectrum SM)
-- ============================================================================
--
-- This section is the E3Controller's own addition. It keeps the one type the
-- legacy RF=1 IQ path still sends: the ecpri_iq_samples codelet captures raw
-- eCPRI sections and the controller sends each one, decompressed and FFT-padded,
-- inline as a Spectrum-IQDataIndication. That path is obsolete (the slot path of
-- the L1-KPM SM replaces it) and this type will be removed with it. Its
-- encoding is unchanged from the previous grammar.
Spectrum-IQDataIndication ::= SEQUENCE {
    iqSamples               OCTET STRING (SIZE (1..16384)),                 -- Raw I/Q data as int16 array
    sampleCount             INTEGER (0..32768),                             -- Number of I/Q samples
    timestamp               INTEGER (0..2147483647) OPTIONAL                -- Unix timestamp when samples were captured
}

END
